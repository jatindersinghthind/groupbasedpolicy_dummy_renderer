/*
 * Copyright (c) 2014 Cisco Systems, Inc. and others.  All rights reserved.
 *
 * This program and the accompanying materials are made available under the
 * terms of the Eclipse Public License v1.0 which accompanies this distribution,
 * and is available at http://www.eclipse.org/legal/epl-v10.html
 */

module apic-provider {
     yang-version 1;
     namespace "urn:opendaylight:params:xml:ns:yang:controller:config:apic-provider";
     prefix "apic-provider";

     import config { prefix config; revision-date 2013-04-05; }

     description
         "This module contains the base YANG definitions for 
          apic-provider services.";

     revision "2014-04-21" {
         description
             "Initial revision.";
     }

     identity apic-provider {
         base "config:service-type";
         config:java-class "org.opendaylight.yang.gen.v1.urn.opendaylight.groupbasedpolicy.apic.rev140528.ApicData";
     }
}
